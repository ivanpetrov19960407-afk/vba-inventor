' External iLogic rule (experimental)
' Draws A3 GOST-like frame + compact Form 3 stamp directly on ActiveSheet sketch.
' No TitleBlockDefinition / BorderDefinition / prompted fields are used.

Option Explicit On

Sub Main()
    ' ===== Constants (sheet units in cm; Inventor internal length unit) =====
    Const SHEET_WIDTH_CM As Double = 42.0      ' A3 landscape width (420 mm)
    Const SHEET_HEIGHT_CM As Double = 29.7     ' A3 landscape height (297 mm)

    Const MARGIN_LEFT_CM As Double = 2.0       ' 20 mm
    Const MARGIN_RIGHT_CM As Double = 0.5      ' 5 mm
    Const MARGIN_TOP_CM As Double = 0.5        ' 5 mm
    Const MARGIN_BOTTOM_CM As Double = 0.5     ' 5 mm

    Const STAMP_WIDTH_CM As Double = 18.5      ' 185 mm
    Const STAMP_HEIGHT_CM As Double = 5.5      ' 55 mm

    Const SKETCH_NAME As String = "RKM_EXP_A3_FORM3"

    Dim app As Inventor.Application = ThisApplication
    Dim drw As Inventor.DrawingDocument = TryCast(app.ActiveDocument, Inventor.DrawingDocument)

    If drw Is Nothing Then
        MessageBox.Show("Откройте чертёж .idw/.dwg и запустите правило снова.", "iLogic: A3 Frame+Stamp")
        Exit Sub
    End If

    Dim sheet As Inventor.Sheet = drw.ActiveSheet
    Dim tg As Inventor.TransientGeometry = app.TransientGeometry

    Dim sk As Inventor.DrawingSketch = GetOrCreateSketch(sheet, SKETCH_NAME)

    sk.Edit()
    ClearSketch(sk)

    ' ---- Outer frame ----
    DrawRectangle(sk, tg, 0.0, 0.0, SHEET_WIDTH_CM, SHEET_HEIGHT_CM)

    ' ---- Inner frame ----
    Dim innerLeft As Double = MARGIN_LEFT_CM
    Dim innerBottom As Double = MARGIN_BOTTOM_CM
    Dim innerRight As Double = SHEET_WIDTH_CM - MARGIN_RIGHT_CM
    Dim innerTop As Double = SHEET_HEIGHT_CM - MARGIN_TOP_CM
    DrawRectangle(sk, tg, innerLeft, innerBottom, innerRight, innerTop)

    ' ---- Compact Form 3 style stamp (bottom-right, inside inner frame) ----
    Dim stampRight As Double = innerRight
    Dim stampBottom As Double = innerBottom
    Dim stampLeft As Double = stampRight - STAMP_WIDTH_CM
    Dim stampTop As Double = stampBottom + STAMP_HEIGHT_CM

    DrawRectangle(sk, tg, stampLeft, stampBottom, stampRight, stampTop)

    ' Main horizontal split: bottom row for signatures/date etc.
    Dim yBottomRow As Double = stampBottom + 1.2
    AddLine(sk, tg, stampLeft, yBottomRow, stampRight, yBottomRow)

    ' Left block + middle columns
    Dim xLeftBlock As Double = stampLeft + 9.0
    AddLine(sk, tg, xLeftBlock, stampBottom, xLeftBlock, stampTop)

    Dim xRole As Double = xLeftBlock + 3.2
    Dim xSign As Double = xRole + 2.1
    Dim xDate As Double = xSign + 2.1
    AddLine(sk, tg, xRole, stampBottom, xRole, stampTop)
    AddLine(sk, tg, xSign, stampBottom, xSign, stampTop)
    AddLine(sk, tg, xDate, stampBottom, xDate, stampTop)

    ' Left block extra split
    Dim yDocInfo As Double = stampBottom + 2.7
    AddLine(sk, tg, stampLeft, yDocInfo, xLeftBlock, yDocInfo)

    ' ---- Static text placeholders ----
    AddText(sk, tg, stampLeft + 0.25, stampTop - 0.55, "НАИМЕНОВАНИЕ ИЗДЕЛИЯ", 0.28)
    AddText(sk, tg, stampLeft + 0.25, yDocInfo - 0.45, "ОБОЗНАЧЕНИЕ ДОКУМЕНТА", 0.28)
    AddText(sk, tg, stampLeft + 0.25, stampBottom + 0.35, "ЛИСТ", 0.28)

    AddText(sk, tg, xLeftBlock + 0.15, stampTop - 0.55, "Лит.", 0.24)
    AddText(sk, tg, xRole + 0.15, stampTop - 0.55, "Подп.", 0.24)
    AddText(sk, tg, xSign + 0.15, stampTop - 0.55, "Дата", 0.24)

    AddText(sk, tg, xLeftBlock + 0.15, stampBottom + 0.35, "Разраб.", 0.24)
    AddText(sk, tg, xRole + 0.15, stampBottom + 0.35, "Пров.", 0.24)
    AddText(sk, tg, xSign + 0.15, stampBottom + 0.35, "Н. контр.", 0.24)
    AddText(sk, tg, xDate + 0.15, stampBottom + 0.35, "Утв.", 0.24)

    sk.ExitEdit()

    MessageBox.Show("Эскиз рамки и штампа создан на активном листе: " & sheet.Name, "iLogic: A3 Frame+Stamp")
End Sub

Private Function GetOrCreateSketch(ByVal sheet As Inventor.Sheet, ByVal sketchName As String) As Inventor.DrawingSketch
    Dim sk As Inventor.DrawingSketch = Nothing

    For Each item As Inventor.DrawingSketch In sheet.Sketches
        If String.Equals(item.Name, sketchName, StringComparison.OrdinalIgnoreCase) Then
            sk = item
            Exit For
        End If
    Next

    If sk Is Nothing Then
        sk = sheet.Sketches.Add()
        sk.Name = sketchName
    End If

    Return sk
End Function

Private Sub ClearSketch(ByVal sk As Inventor.DrawingSketch)
    Dim textCount As Integer = sk.SketchTexts.Count
    For i As Integer = textCount To 1 Step -1
        sk.SketchTexts.Item(i).Delete()
    Next

    Dim lineCount As Integer = sk.SketchLines.Count
    For i As Integer = lineCount To 1 Step -1
        sk.SketchLines.Item(i).Delete()
    Next
End Sub

Private Sub DrawRectangle(ByVal sk As Inventor.DrawingSketch, ByVal tg As Inventor.TransientGeometry, _
                          ByVal x1 As Double, ByVal y1 As Double, ByVal x2 As Double, ByVal y2 As Double)
    AddLine(sk, tg, x1, y1, x2, y1)
    AddLine(sk, tg, x2, y1, x2, y2)
    AddLine(sk, tg, x2, y2, x1, y2)
    AddLine(sk, tg, x1, y2, x1, y1)
End Sub

Private Sub AddLine(ByVal sk As Inventor.DrawingSketch, ByVal tg As Inventor.TransientGeometry, _
                    ByVal x1 As Double, ByVal y1 As Double, ByVal x2 As Double, ByVal y2 As Double)
    Dim p1 As Inventor.Point2d = tg.CreatePoint2d(x1, y1)
    Dim p2 As Inventor.Point2d = tg.CreatePoint2d(x2, y2)
    sk.SketchLines.AddByTwoPoints(p1, p2)
End Sub

Private Sub AddText(ByVal sk As Inventor.DrawingSketch, ByVal tg As Inventor.TransientGeometry, _
                    ByVal x As Double, ByVal y As Double, ByVal textValue As String, ByVal textHeightCm As Double)
    Dim p As Inventor.Point2d = tg.CreatePoint2d(x, y)
    Dim st As Inventor.SketchText = sk.SketchTexts.AddFitted(p, textValue)
    st.Height = textHeightCm
End Sub
